module use-case {
  namespace "http://opennetworking.org/enterprise/use-case";
  prefix uc;

  import device-group{ prefix dg; }  
  import site{ prefix st; }
  import enterprise{ prefix ent; }
  import application{ prefix app; }
  import visibility{ prefix vis; }
  import qos{ prefix qos; }

  organization "Open Networking Foundation.";
  contact "Scott Baker";
  description "To generate JSON from this use command
    pyang -f jtoxx test1.yang | python3 -m json.tool > test1.json
    Copied from YangUIComponents project";

  revision "2020-11-18" {
    description "An Aether Use Case";
    reference "RFC 6087";
  }

  typedef use-case-id {
        type string {
            length 1..32;
        }
  }

  container use-case {
    description "The top level container";

    list use-case {
      key "id";
      description
        "List of use cases";

      leaf id {
        type use-case-id;
        description "ID for this use case.";
      }

      leaf display-name {
        type string {
            length 1..80;
        }
        description "display name to use in GUI or CLI";
      }     

      leaf description {
        type string {
          length 1..100;
        }
        description "description of this site";
      }

      leaf enterprise {
        type leafref {
          path "/ent:enterprise/ent:enterprise/ent:id";
        }          
        description
          "Link to enterprise that owns this use case";
      }

      list device-group {
        key "device-group";
        leaf device-group {
          type leafref {
            path "/dg:device-group/dg:device-group/dg:id";
          }            
          description
              "Link to device group that is authorized to participate in this use case";
        }
        leaf allowed {
          type boolean;
          default true;
          description
            "Allow or disallow this device group to participate in the use case";
        }
      }

      list site {
        key "site";
        leaf site {
          type leafref {
            path "/st:site/st:site/st:id";
          }            
          description
              "Link to site that is authorized to participate in this use case";
        }
        leaf allowed {
          type boolean;
          default true;
          description
            "Allow or disallow this site to participate in the use case";
        }
      }

      list application {
        key "application";
        leaf application {
          type leafref {
            path "/app:application/app:application/app:id";
          }            
          description
              "Link to an appplcation that is authorized to participate in this use case";
        }
        leaf allowed {
          type boolean;
          default true;
          description
            "Allow or disallow this application to participate in the use case";
        }
      }

      list visibility {
        key "visibility";
        leaf visibility {
          type leafref {
            path "/vis:visibility/vis:visibility/vis:id";
          }            
          description
              "Link to an visibility profile that is authorized to participate in this use case";
        }
        leaf allowed {
          type boolean;
          default true;
          description
            "Allow or disallow this visibility profile to participate in the use case";
        }
      }

      list qos {
        key "qos";
        leaf qos {
          type leafref {
            path "/qos:qos/qos:qos/qos:id";
          }            
          description
              "Link to an qos profile that is authorized to participate in this use case";
        }
        leaf allowed {
          type boolean;
          default true;
          description
            "Allow or disallow this qos profile to participate in the use case";
        }
      } 

    }
  } 
}
