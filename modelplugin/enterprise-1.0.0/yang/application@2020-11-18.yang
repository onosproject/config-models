module application {
  namespace "http://opennetworking.org/enterprise/application";
  prefix app;

  import deployment-environment{ prefix de; }
  import qos{ prefix qos; }
  import ietf-inet-types{ prefix ietf; }

  organization "Open Networking Foundation.";
  contact "Scott Baker";
  description "To generate JSON from this use command
    pyang -f jtoxx test1.yang | python3 -m json.tool > test1.json
    Copied from YangUIComponents project";

  revision "2020-11-18" {
    description "Aether Application.";
    reference "RFC 6087";
  }

  typedef application-id {
        type string {
            length 1..32;
        }
  }

  container application {
    description "The top level container";

    list application {
      key "id";
      description
        "List of applications";

      leaf id {
        type application-id;
        description "ID for this application.";
      }

      leaf display-name {
        type string {
            length 1..80;
        }
        description "display name to use in GUI or CLI";
      }

      leaf description {
        type string {
          length 1..100;
        }
        description "description of this application";
      }

      leaf deployment-environment {
        type leafref {
          path "/de:deployment-environment/de:deployment-environment/de:id";
        }          
        description
          "Link to site that contains this deployment environment";
      }

      list endpoint {
        key "name";
        leaf name {
          type string;
          description
              "Name of this endpoint";
        }
        leaf hostname {
          type ietf:host;
          description
              "Hostname of this endpoint";
        }
        leaf port {
          type ietf:port-number;
          description
              "Port number of this endpoint";
        }
      }

      list qos {
        key "qos";
        leaf qos {
          type leafref {
            path "/qos:qos/qos:qos/qos:id";
          }            
          description
              "Link to an qos profile that the application requests be used";
        }
        leaf allowed {
          type boolean;
          default true;
          description
            "Allow or disallow this qos profile to participate in the use case";
        }
      }
    }
  } 
}
