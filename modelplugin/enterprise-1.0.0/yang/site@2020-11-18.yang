module site {
  namespace "http://opennetworking.org/enterprise/site";
  prefix site;

  import enterprise{ prefix ent; }

  organization "Open Networking Foundation.";
  contact "Scott Baker";
  description "To generate JSON from this use command
    pyang -f jtoxx test1.yang | python3 -m json.tool > test1.json
    Copied from YangUIComponents project";

  revision "2020-11-18" {
    description "An Aether Site";
    reference "RFC 6087";
  }

  typedef site-id {
        type string {
            length 1..32;
        }
  }

  container site {
    description "The top level container";

    list site {
      key "id";
      description
        "List of sites";

      leaf id {
        type site-id;
        description "ID for this site.";
      }

      leaf display-name {
        type string {
            length 1..80;
        }
        description "display name to use in GUI or CLI";
      }     

      leaf description {
        type string {
          length 1..100;
        }
        description "description of this site";
      }

      leaf enterprise {
        type leafref {
          path "/ent:enterprise/ent:enterprise/ent:id";
        }          
        description
          "Link to enterprise that owns this site";
      }
    }
  } 
}
