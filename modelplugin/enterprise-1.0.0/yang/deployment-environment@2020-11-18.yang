module deployment-environment {
  namespace "http://opennetworking.org/enterprise/deployment-environment";
  prefix deployment-environment;

  import site{ prefix st; }

  organization "Open Networking Foundation.";
  contact "Scott Baker";
  description "To generate JSON from this use command
    pyang -f jtoxx test1.yang | python3 -m json.tool > test1.json
    Copied from YangUIComponents project";

  revision "2020-11-18" {
    description "Deployment environment within a site where applications can be deployed. Potentially a Projects or a Cluster.";
    reference "RFC 6087";
  }

  typedef deployment-environment-id {
        type string {
            length 1..32;
        }
  }

  container deployment-environment {
    description "The top level container";

    list deployment-environment {
      key "id";
      description
        "List of deployment environments";

      leaf id {
        type deployment-environment-id;
        description "ID for this deployment environment.";
      }

      leaf display-name {
        type string {
            length 1..80;
        }
        description "display name to use in GUI or CLI";
      }

      leaf cluster-name {
        type string {
            length 1..80;
        }
        description "cluster name that corresponds to this deployment environment";
      }    

      leaf description {
        type string {
          length 1..100;
        }
        description "description of this deployment environment";
      }

      leaf site {
        type leafref {
          path "/st:site/st:site/st:id";
        }          
        description
          "Link to site that contains this deployment environment";
      }
    }
  } 
}
