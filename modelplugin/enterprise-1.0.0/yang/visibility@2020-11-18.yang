module visibility {
  namespace "http://opennetworking.org/enterprise/visibility";
  prefix vis;

  import application{ prefix app; }

  organization "Open Networking Foundation.";
  contact "Scott Baker";
  description "To generate JSON from this use command
    pyang -f jtoxx test1.yang | python3 -m json.tool > test1.json
    Copied from YangUIComponents project";

  revision "2020-11-18" {
    description "Aether Visibility Profile.";
    reference "RFC 6087";
  }

  typedef visibility-id {
        type string {
            length 1..32;
        }
  }

  container visibility {
    description "The top level container";

    list visibility {
      key "id";
      description
        "List of visibility profiles";

      leaf id {
        type visibility-id;
        description "ID for this visibility profile.";
      }

      leaf display-name {
        type string {
            length 1..80;
        }
        description "display name to use in GUI or CLI";
      }

      leaf description {
        type string {
          length 1..100;
        }
        description "description of this visibility profile";
      }

      leaf application {
        type leafref {
          path "/app:application/app:application/app:id";
        }          
        description
          "Link to application this visibility profile will be applied to";
      }        
    }
  } 
}
