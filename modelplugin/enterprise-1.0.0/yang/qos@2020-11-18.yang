module qos {
  namespace "http://opennetworking.org/enterprise/qos";
  prefix qos;

  organization "Open Networking Foundation.";
  contact "Scott Baker";
  description "To generate JSON from this use command
    pyang -f jtoxx test1.yang | python3 -m json.tool > test1.json
    Copied from YangUIComponents project";

  revision "2020-11-18" {
    description "Aether QoS Profile.";
    reference "RFC 6087";
  }

  typedef qos-id {
        type string {
            length 1..32;
        }
  }

  container qos {
    description "The top level container";

    list qos {
      key "id";
      description
        "List of qos profiles";

      leaf id {
        type qos-id;
        description "ID for this qos profile.";
      }

      leaf display-name {
        type string {
            length 1..80;
        }
        description "display name to use in GUI or CLI";
      }

      leaf description {
        type string {
          length 1..100;
        }
        description "description of this visibility profile";
      }

      container connectivity-service {
        container apn-ambr {
          leaf uplink {
            type uint32 {
              range 0..4294967295;
            }
            default 0;
            units bps;
            description
              "Upstream aggregate maximum bit rate";
          }
          leaf downlink {
            type uint32 {
              range 0..4294967295;
            }
            default 0;
            units bps;
            description
              "Downstream aggregate maximum bit rate";
          }        
        }
      }
    }
  } 
}
