module e2node {
  yang-version 1.1;
  namespace "http://opennetworking.org/oran/e2node";
  prefix e2;

  include e2node-o-cu-cp;
  include e2node-o-cu-up;
  include e2node-o-du;

  organization "Open Networking Foundation.";
  contact "Sean Condon";
  description "Configuration of E2Nodes
    To generate JSON from this use command
    pyang -f jtoxx e2node.yang | python3 -m json.tool > test1.json";

  revision "2020-05-01" {
    description "Initial Version";
    reference "ORAN-WG3.E2GAP-V01.00";
  }

  feature handover {
    description "The E2Node supports the handover feature";
  }

  feature load-balancing {
    description "The E2Node supports the load-balancing feature";
  }

  container e2node {
    description "The top level container";
    
    container intervals {
        description "Intervals for E2 services";

        leaf RadioMeasReportPerUe {
            type uint32;
            units ms;
            description "Interval for report of RadioMeasReportPerUe";
            default 10;
        }
        
        leaf RadioMeasReportPerCell {
            type uint32;
            units ms;
            description "Interval for report of RadioMeasReportPerUe";
            default 10;
        }
        
        leaf SchedMeasReportPerUe {
            type uint32;
            units ms;
            description "Interval for report of SchedMeasReportPerUe";
            default 10;
        }
        
        leaf SchedMeasReportPerCell {
            type uint32;
            units ms;
            description "Interval for report of SchedMeasReportPerCell";
            default 10;
        }
        
        leaf PdcpMeasReportPerUe {
            type uint32;
            units ms;
            description "Interval for report of PdcpMeasReportPerUe";
            default 10;
        }
   
    }

    container example-container {
        description "A YANG container for demo purposes.";

        leaf max-handover-rate {
            if-feature handover;
            config false;
            type uint32;
            units ho/sec;
            description "If the handover feature is present this is the number
            of handovers/sec that the E2Node says it can support. It is not
            settable as it given as an example of a limitation of the hardware";
        }

        leaf max-ues {
          if-feature load-balancing;
          type uint32;
          description "If the load-balancing feature is present, this is the
          maximum number of UEs that the E2 node will accept. It is settable, and
          so can be changed at runtime.";
        }

    }

  }
}
