submodule e2node-o-cu-up {
  yang-version 1.1;
  belongs-to e2node {
    prefix up;
  }

  organization "Open Networking Foundation.";
  contact "Sean Condon";
  description "Configuration of E2Node Central Unit User Plane";

  revision "2020-05-01" {
    description "Initial version";
    reference "ORAN-WG3.E2GAP-V01.00";
  }

  container e2-up {
    presence "CU-UP is present";
    description "Configuration related to CU-UP";

  }
}
