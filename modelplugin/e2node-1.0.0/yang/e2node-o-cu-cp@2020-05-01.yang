submodule e2node-o-cu-cp {
  yang-version 1.1;
  belongs-to e2node {
    prefix cp;
  }

  organization "Open Networking Foundation.";
  contact "Sean Condon";
  description "Configuration of E2Node Central Unit Control Plane";

  revision "2020-05-01" {
    description "Initial version";
    reference "ORAN-WG3.E2GAP-V01.00";
  }

  container e2-cp {
    presence "CU-CP is present";
    description "Configuration related to CU-CP";

    leaf handover-5g {
        if-feature handover;
        config false;
        type boolean;
        description "An example of a handover only attribute non-settable. It's
        related only to the CU-UP, so is in this submodule";
    }
  }
}
