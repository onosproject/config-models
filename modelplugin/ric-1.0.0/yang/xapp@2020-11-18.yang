module xapp {
  namespace "http://opennetworking.org/oran/xapp";
  prefix xapp;

  organization
    "Open Networking Foundation";
  contact
    "Adib Rastegarnia";
  description
    "Configuration of xApps
     To generate JSON from this use command
     pyang -f jtox xapp@2020-11-18.yang | python3 -m json.tool > test1.json";

  revision 2020-11-18 {
    description
      "Initial Version";
    reference
      "O-RAN-OAM-architecture-Specification (O1)";
  }

  grouping xapp-config {
    leaf name {
      type string;
      description
        "Name of the xapp";
    }
    leaf version {
      type string;
      description
        "version of the xapp";
    }
    description
      "xApp configuration";
  }

  container xapps {
    list xapp {
      key "name";
      uses xapp-config;
      description
        "xApp configuration";
    }
    description
      "List of xApps to be configured.";
  }
}
