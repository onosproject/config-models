module aether-connectivity-profile {
  namespace "http://opennetworking.org/aether/connectivity-profile";
  prefix pro;

  organization "Open Networking Foundation.";
  contact "Scott Baker";
  description "To generate JSON from this use command
    pyang -f jtoxx test1.yang | python3 -m json.tool > test1.json
    Copied from YangUIComponents project";

  revision "2020-07-15" {
    description "An Aether Connectivity Profile";
    reference "RFC 6087";
  }

  typedef proid {
        type string {
            length 32;
        }
  }

  container connectivity-profile {
    description "The top level container";

    list connectivity-profile {
      key "uuid";
      description
        "List of profiles";

      leaf uuid {
        type proid;
        description "UUID for this profile";
      }

      container contents {
         description "Contents of the profile";

         leaf bandwidth {
           type uint32 {
             range 0..100000000;
           }
           units bps;
           default 1000000;
           description
             "Bandwidth limit for this profile. This is just
             an example/placeholder for where real profile fields
             will be placed";
         }
      }
    }
  } 
}
