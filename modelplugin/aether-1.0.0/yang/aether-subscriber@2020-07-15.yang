module aether-subscriber {
  namespace "http://opennetworking.org/aether/subscriber";
  prefix sub;

  organization "Open Networking Foundation.";
  contact "Scott Baker";
  description "To generate JSON from this use command
    pyang -f jtoxx test1.yang | python3 -m json.tool > test1.json
    Copied from YangUIComponents project";

  revision "2020-07-15" {
    description "An Aether Subscriber";
    reference "RFC 6087";
  }

  typedef ueid {
        type string {
            length 1..15;
        }
  }

  container subscriber {
    description "The top level container";

    list ue {
      key "ueid";
      description
        "List of subscriber devices";

      leaf ueid {
        type ueid;
        description "identifier for this subscriber, may or may not be an IMSI";
      }

      leaf enabled {
        type boolean;
        default false;
        description
          "Enable or disable this ue";
      }
    }
  } 
}
