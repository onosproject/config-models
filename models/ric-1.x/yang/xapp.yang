module xapp {
  namespace "http://opennetworking.org/oran/xapp";
  prefix xapp;

  import ietf-inet-types {
    prefix inet;
  }

  organization
    "Open Networking Foundation.";
  contact
    "Adib Rastegarnia";
  description
    "To generate JSON from this use command
     pyang -f jtoxx xapp.yang | python3 -m json.tool > test1.json
     Copied from YangUIComponents project";

  revision 2020-11-24 {
    description
      "Add e2 node configuration information and list of e2 nodes";
    reference
      "";
  }

  grouping e2node-info {
    description
      "The top level container";
    leaf ip {
      type inet:ip-address;
      description
        "The IP address of the node";
    }
    leaf port {
      type inet:port-number;
      description
        "The port of the node";
    }
    leaf plmn-id {
      type string;
      description
        "PLMN id";
    }
    leaf id {
      type string;
      description
        "eNB id";
    }
  }

  container nodes {
    config false;
    list node {
      key "id";
      uses e2node-info;
      description
        "e2 node";
    }
    description
      "The list of e2 nodes";
  }
}
