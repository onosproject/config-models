module onf-switch-model {
  namespace "http://opennetworking.org/devicesim/test-switch-model";
  prefix sm;

  import onf-switch-types {
    prefix st;
  }
  import ietf-yang-types {
    prefix yt;
  }
  import onf-extension-types {
    prefix xt;
  }

  organization
    "Open Networking Foundation";
  contact
    "ROC Engineering";
  description
    "Configuration of switch components.
     To generate JSON from this use command
     pyang -f jtoxx sd-fabric.yang | python3 -m json.tool > test1.json";

  revision 2023-03-07 {
    description
      "Initial import";
    reference
      "inspired by sd-fabric";
  }

  list switch-model {
    xt:group-tag "Underlay";
    key "switch-model-id";
    description
      "A model of switch - here the switch models are like a library of preconfigured switch.
       They are referred to by the 'switch' instances, and give a template of ports and port speeds
       that may be used when configuring switches.
       Here we give it a description and a display-name, and also a map of attributes that
       may be used to arbitarilily assign values at runtime";
    leaf switch-model-id {
      type yt:yang-identifier {
        length "1..100";
      }
      description
        "unique identifier for the switch";
    }
    uses st:desc-display-name;
    uses st:map-of-attributes;
    list port {
      key "cage-number";
      description
        "A port in a switch - this demonstrates a list within a list. Each port has a description
         and a display-name";
      leaf cage-number {
        type uint8;
        description
          "identifier of the cage - physical port on switch";
      }
      leaf max-channel {
        type uint8 {
          range "0..16";
        }
        default "0";
        description
          "A splitter can divide the port in to channels.
           The default value 0 indicates the port is not channelizable";
      }
      uses st:desc-display-name;
      leaf-list speeds {
        type identityref {
          base st:speed;
        }
        min-elements 1;
        description
          "port speed - these are all the supported speeds on this port, and demonstrates a practical
           use for the leaf-list. Rather than using enum it is using an Identity, and will accept any
           Identity that is based off the 'speed' identity in onf-switch-types";
      }
    }
  }
}
