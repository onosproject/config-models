module onf-test1-identities {
  namespace "http://opennetworking.org/devicesim/test1-identities";
  prefix t1id;

  organization
    "Open Networking Foundation.";
  contact
    "Sean Condon";
  description
    "Identities related to for testdevice-2.0.0";

  revision 2020-09-01 {
    description
      "Initial Version";
    reference
      "onos unit testing";
  }

  identity MYBASE {
    description
      "a BASE identity type";
  }

  identity IDTYPE1 {
    base MYBASE;
    description
      "A derived identity based off MYBASE";
  }

  identity IDTYPE2 {
    base MYBASE;
    description
      "A SECOND derived identity based off MYBASE";
  }
}
