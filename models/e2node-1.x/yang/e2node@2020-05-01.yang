module e2node {
  namespace "http://opennetworking.org/oran/e2node";
  prefix e2;

  organization
    "Open Networking Foundation.";
  contact
    "Sean Condon";
  description
    "Configuration of E2Nodes
     To generate JSON from this use command
     pyang -f jtoxx e2node.yang | python3 -m json.tool > test1.json";

  revision 2020-05-01 {
    description
      "Initial Version";
    reference
      "ORAN-WG3.E2GAP-V01.00";
  }

  container e2node {
    description
      "The top level container";
    container intervals {
      description
        "Intervals for E2 services";
      leaf RadioMeasReportPerUe {
        type uint32;
        units "ms";
        description
          "Interval for report of RadioMeasReportPerUe";
        default "10";
      }
      leaf RadioMeasReportPerCell {
        type uint32;
        units "ms";
        description
          "Interval for report of RadioMeasReportPerUe";
        default "10";
      }
      leaf SchedMeasReportPerUe {
        type uint32;
        units "ms";
        description
          "Interval for report of SchedMeasReportPerUe";
        default "10";
      }
      leaf SchedMeasReportPerCell {
        type uint32;
        units "ms";
        description
          "Interval for report of SchedMeasReportPerCell";
        default "10";
      }
      leaf PdcpMeasReportPerUe {
        type uint32;
        units "ms";
        description
          "Interval for report of PdcpMeasReportPerUe";
        default "10";
      }
    }
  }
}
