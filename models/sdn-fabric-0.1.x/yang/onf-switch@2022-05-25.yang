// SPDX-FileCopyrightText: 2022-present Intel Corporation
//
// SPDX-License-Identifier: Apache-2.0

module onf-switch {
  namespace "http://opennetworking.org/oran/onf-switch";
  prefix sw;

  import onf-sdn-fabric-types { prefix st; }
  import onf-switch-model { prefix sm; }
  import ietf-inet-types{ prefix inet; }
  import ietf-yang-types{ prefix yt; }

  include onf-switch-port;
  include onf-switch-pair;
  include onf-switch-vlan;

  organization "Intel Corporation";
  contact "ROC Engineering";
  description "Configuration of switch components";

  revision "2022-05-25" {
    description "Initial Version";
    reference "ROC SD-Fabric Notes";
  }

  list switch {
    key "switch-id";
    description "A managed device in the fabric";

    leaf switch-id {
      type inet:domain-name;
      description "unique identifier for the switch";
    }

    uses st:desc-display-name;

    uses st:map-of-attributes;

    leaf model-id {
        type leafref {
          path "/sm:switch-model/sm:switch-model-id";
        }
        mandatory true;
        description "link to switch model";
    }

    leaf role {
        type enumeration {
            enum undefined {
                value 0;
                description "Unknown role";
            }
            enum leaf {
                value 1;
                description "Leaf role";
            }
            enum spine {
                value 2;
                description "Spine role";
            }
        }
        mandatory true;
        description "The role of the switch in the fabric";
    }

    container management {
        leaf address {
          type inet:domain-name;
          description "The management IPv4 address or host or service name";
        }

        leaf port-number {
          type inet:port-number;
          description "The mangement port number";
        }

        description "configuration of the management port";
    }

    uses ports-grouping;

    uses switch-pair-grouping;

    uses vlan-grouping;

    container state {
      config false;

      leaf connected {
        type string;
        description "status of the port: up|down";
      }
      leaf last-connected {
        type yt:date-and-time;
        description "Last known time the switch was connected";
      }
      description "Op state attributes";
    }
  }
}
