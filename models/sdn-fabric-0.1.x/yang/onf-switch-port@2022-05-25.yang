// SPDX-FileCopyrightText: 2022 Intel Corporation
//
// SPDX-License-Identifier: Apache-2.0

submodule onf-switch-port {
  belongs-to onf-switch { prefix sw; }

  import onf-sdn-fabric-types { prefix st; }
  import onf-switch-model { prefix sm; }
  import onf-dhcp-server { prefix dhcp; }
  import openconfig-interfaces { prefix ocif; }

  include onf-switch-vlan;

  organization "Intel Corporation";
  contact "ROC Engineering";
  description "Configuration of port within switch";

  revision "2022-05-25" {
    description "Initial Version";
    reference "ROC SD-Fabric Notes";
  }

  grouping ports-grouping {
    list port {
      key "cage-number channel-number";
      description "A port in a switch";

      st:node-extension;

      leaf cage-number {
        st:leaf-selection "/switch-model[@switch-model-id=$this/../../model-id]/port/@cage-number";
        must "set-contains(/switch-model[@switch-model-id=$this/../../model-id]/port/@cage-number, .)" {
          error-message "port cage-number must be present in corresponding switch-model/port";
          description "port cage-number must be from the corresponding switch-model";
        }
        type leafref {
          path "/sm:switch-model/sm:port/sm:cage-number";
        }
        description "reference to the cage-number of the port in the switch model";
      }

      leaf channel-number {
        must "number(.) <= number(/switch-model[@switch-model-id=$this/../../model-id]/port[@cage-number=$this/../@cage-number]/max-channel)" {
          error-message "port channel-number exceeds max-channel of corresponding switch-model/port";
          description "port channel-number must be equal or less than max-channel in corresponding switch-model/port";
        }
        type uint8 {
          range 0..16;
        }
        description "reference to the channel-number of the port in the switch model.
        The value cannot exceed the max-channels of the corresponding port in the switch-model";
      }

      uses st:desc-display-name;

      leaf speed {
        st:leaf-selection "/switch-model[@switch-model-id=$this/../../model-id]/port[@cage-number=$this/../@cage-number]/speeds";
        must "contains(/switch-model[@switch-model-id=$this/../../model-id]/port[@cage-number=$this/../@cage-number]/speeds, string($this))" {
          error-message "port speed must be present in corresponding switch-model/port";
          description "port speed must be from the corresponding switch-model";
        }
        type identityref {
          base st:speed;
        }
        mandatory true;
        description "configured port speed";
      }

      leaf-list dhcp-connect-point {
        type leafref {
          path "/dhcp:dhcp-server/dhcp:dhcp-server-id";
        }
        description "Reference to DHCP connect point";
      }

      container vlans {
        st:node-extension;
        st:leaf-selection "vlans test";
        leaf untagged {
          type leafref {
            path "../../../sw:vlan/sw:vlan-id";
          }
          default 1;
          description "vlan for untagged packets";
        }
        leaf-list tagged {
          type leafref {
            path "../../../sw:vlan/sw:vlan-id";
          }
          description "multiple tagged vlans";
        }
        description "untagged and tagged vlans per port";
      }

      container state {
        config false;

        uses ocif:interface-common-state;

        description "Op state attributes";
      }
    }
    description "ports grouping";
  }
}
