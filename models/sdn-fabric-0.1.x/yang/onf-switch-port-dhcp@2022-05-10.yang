// SPDX-FileCopyrightText: 2022 Intel Corporation
//
// SPDX-License-Identifier: Apache-2.0

submodule onf-switch-port-dhcp {
  belongs-to onf-switch { prefix sw; }

  import ietf-inet-types { prefix inet; }

  organization "Intel Corporation";
  contact "ROC Engineering";
  description "Configuration of dhcp within port within switch";

  revision "2022-05-10" {
    description "Initial Version";
    reference "ROC SD-Fabric Notes";
  }

  grouping dhcp {
    leaf-list dhcp-connect-point {
      type inet:ipv4-address-no-zone;
      description "a list of ip addresses";
    }
    description "reusable dhcp configuration";
  }

}
