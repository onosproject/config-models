// SPDX-FileCopyrightText: 2022 Intel Corporation
//
// SPDX-License-Identifier: Apache-2.0

submodule onf-switch-port {
  belongs-to onf-switch { prefix sw; }

  import onf-sdn-fabric-types { prefix st; }
  import onf-switch-model { prefix sm; }
  import onf-port-types { prefix pt; }

  include onf-switch-port-dhcp;

  organization "Intel Corporation";
  contact "ROC Engineering";
  description "Configuration of port within switch";

  revision "2022-05-10" {
    description "Initial Version";
    reference "ROC SD-Fabric Notes";
  }

  grouping ports {
    list port {
      key "cage-number channel-number";
      description "A port in a switch";

      leaf cage-number {
        type leafref {
          path "/sm:switch-model/sm:port/sm:cage-number";
        }
        description "reference to the cage-number of the port in the switch model";
      }

      leaf channel-number {
        type leafref {
          path "/sm:switch-model/sm:port/sm:channel-number";
        }
        description "reference to the channel-number of the port in the switch model";
      }

      uses st:desc-display-name;

      leaf speed {
        type identityref {
          base pt:speed;
        }
        description "configured port speed";
      }

      uses dhcp;
    }
    description "ports grouping";
  }
}
