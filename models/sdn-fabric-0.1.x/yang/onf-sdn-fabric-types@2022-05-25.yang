// SPDX-FileCopyrightText: 2021 Open Networking Foundation
//
// SPDX-License-Identifier: Apache-2.0

module onf-sdn-fabric-types {
  namespace "http://opennetworking.org/aether/onf-sdn-fabric-types";
  prefix ft;

  import ietf-yang-types{ prefix yt; }

  organization "Intel Corporation";
  contact "ROC Engineering";
  description "A set of base types for SDN Fabric modeling.";

  revision "2022-05-25" {
    description "SDN Fabric Base Types";
    reference "RFC 6087";
  }

  extension leaf-selection {
    argument selection-stmt;
    description "An Xpath statement that gives a selection criteria for leaf values";
  }

  extension node-extension {
    description "an example of a nod extension without any argument";
  }

  typedef vlan {
    type uint16 {
      range 0..4096;
    }
    description "a 12 bit VLAN identifier";
  }

  grouping desc-display-name {
    description "reusable leafs for description and display-name";
    leaf display-name {
      type string {
        length 1..80;
      }
      description "display name to use in GUI or CLI";
    }

    leaf description {
      type string {
        length 1..1024;
      }
      description "long description field";
    }
  }

  grouping map-of-attributes {
    list attribute {
      key "attribute-key";

      leaf attribute-key {
        type yt:yang-identifier {
          length 1..40;
        }
        description "the key in a map of attributes";
      }

      leaf value {
        type string {
          length 1..200;
        }
        mandatory true;
        description "the value of attribute-key";
      }
      description "a map of extra attributes: string-string";
    }
    description "Reusable map of attributes";
  }

  // Port speeds
  identity speed {
    description "base identity of port speeds";
  }

  identity speed-autoneg {
    base speed;
    description "Auto-negotiate";
  }

  identity speed-1g {
    base speed;
    description "1 Gbps";
  }

  identity speed-2-5g {
    base speed;
    description "2.5 Gbps";
  }

  identity speed-5g {
    base speed;
    description "5 Gbps";
  }

  identity speed-10g {
    base speed;
    description "10 Gbps";
  }

  identity speed-25g {
    base speed;
    description "25 Gbps";
  }

  identity speed-40g {
    base speed;
    description "40 Gbps";
  }

  identity speed-100g {
    base speed;
    description "100 Gbps";
  }

  identity speed-400g {
    base speed;
    description "400 Gbps";
  }
}
